SPKAC-Schema DEFINITIONS AUTOMATIC TAGS ::=
BEGIN
    IMPORTS

    AlgorithmIdentifier{}, SIGNATURE-ALGORITHM
    FROM AlgorithmInformation-2009
        {iso(1) identified-organization(3) dod(6) internet(1)
        security(5) mechanisms(5) pkix(7) id-mod(0)
        id-mod-algorithmInformation-02(58)}

    SubjectPublicKeyInfo, SignatureAlgorithms
    FROM PKIX1Explicit-2009
        {iso(1) identified-organization(3) dod(6) internet(1)
        security(5) mechanisms(5) pkix(7) id-mod(0)
        id-mod-pkix1-explicit-02(51)};

    PublicKeyAndChallenge ::= SEQUENCE
    {
    spki SubjectPublicKeyInfo,
    challenge IA5String
    }
    SignedPublicKeyAndChallenge ::= SEQUENCE
    {
    publicKeyAndChallenge PublicKeyAndChallenge,
    signatureAlgorithm AlgorithmIdentifier{SIGNATURE-ALGORITHM,
                                {SignatureAlgorithms}},
    signature BIT STRING
    }

END
